Attribute VB_Name = "Create2DLineForm"
Attribute VB_Base = "0{C29B06D9-F433-4232-8BE3-621240FC34B8}{DA7B0DA6-38D8-4323-951E-AB469118E4AD}"
Attribute VB_GlobalNameSpace = False
Attribute VB_Creatable = False
Attribute VB_PredeclaredId = True
Attribute VB_Exposed = False
Attribute VB_TemplateDerived = False
Attribute VB_Customizable = False
Private Sub okButton_Click()
    Dim x1 As Double
    Dim y1 As Double
    Dim x2 As Double
    Dim y2 As Double
    x1 = x1TextBox.Value
    mainForm.lineX1 = x1
    y1 = y1TextBox.Value
    mainForm.lineY1 = y1
    x2 = x2TextBox.Value
    mainForm.lineX2 = x2
    y2 = y2TextBox.Value
    mainForm.lineY2 = y2
    
    mainForm.CreateLine x1, y1, 0, x2, y2, 0
    ThisDrawing.SendCommand " "
    ZoomAll
    
    mainForm.isAB = True
    
    mainForm.statusTextBox.Value = mainForm.statusTextBox.Value & "A 2D LINE has just created by (" & x1 & "," & y1 & ") and (" & x2 & "," & y2 & ")" & vbCrLf
    mainForm.statusTextBox.Value = mainForm.statusTextBox.Value & "At: " & Now() & vbCrLf & vbCrLf
    mainForm.abLabel.Caption = "A(" & x1 & ", " & y1 & "); B(" & x2 & ", " & y2 & ")"
    
    Create2DLineForm.Hide
End Sub

Attribute VB_Name = "Create2DPointForm"
Attribute VB_Base = "0{ED6842E0-3B12-4BD6-A930-33E16782FFDE}{156246DA-A0D1-4A26-94FD-76F87C1D3A6D}"
Attribute VB_GlobalNameSpace = False
Attribute VB_Creatable = False
Attribute VB_PredeclaredId = True
Attribute VB_Exposed = False
Attribute VB_TemplateDerived = False
Attribute VB_Customizable = False
Private Sub okButton_Click()
    Dim x As Double
    Dim y As Double
    x = xTextBox.Value
    mainForm.pointX = x
    y = yTextBox.Value
    mainForm.pointY = y
    pointZ = 0
    
    mainForm.CreatePoints x, y, 0
    ThisDrawing.SendCommand " "
    ZoomAll
    
    mainForm.isC = True
    
    mainForm.statusTextBox.Value = mainForm.statusTextBox.Value & "A 2D POINT has just created with (" & x & "," & y & ")" & vbCrLf
    mainForm.statusTextBox.Value = mainForm.statusTextBox.Value & "At: " & Now() & vbCrLf & vbCrLf
    mainForm.cLabel.Caption = "C(" & x & ", " & y & ")"
    
    Create2DPointForm.Hide
End Sub

Attribute VB_Name = "Module1"
Public Sub VBASimpleDrawing()
    mainForm.show
End Sub

Attribute VB_Name = "mainForm"
Attribute VB_Base = "0{DF31F3DA-BBA6-49C3-968F-1B13224A3F9D}{E5A3E63C-8E99-407C-8EFD-7504A29F0D77}"
Attribute VB_GlobalNameSpace = False
Attribute VB_Creatable = False
Attribute VB_PredeclaredId = True
Attribute VB_Exposed = False
Attribute VB_TemplateDerived = False
Attribute VB_Customizable = False
'Line AB
Public lineX1 As Double
Public lineY1 As Double
Public lineZ1 As Double
Public lineX2 As Double
Public lineY2 As Double
Public lineZ2 As Double
Public isAB As Boolean

Dim abNVector1 As Double
Dim abNVector2 As Double
Dim abUVector1 As Double
Dim abUVector2 As Double

'Point C
Public pointX As Double
Public pointY As Double
Public pointZ As Double
Public isC As Boolean

'Point D
Public dX As Double
Public dY As Double
Public dZ As Double

'Point E
Public eX As Double
Public eY As Double
Public eZ As Double

'Point F
Public fX As Double
Public fY As Double
Public fZ As Double

Public Sub CreateTextFile(str)
'PURPOSE: Create A New Text File
'SOURCE: www.TheSpreadsheetGuru.com

Dim TextFile As Integer
Dim FilePath As String

'What is the file path and name for the new text file?
    FilePath = "C:\Users\" & Environ("username") & "\Desktop\Log.txt"

'Determine the next file number available for use by the FileOpen function
    TextFile = FreeFile

'Open the text file
    Open FilePath For Append As TextFile

'Write some lines of text
    Print #TextFile, "---------------------------------------------"
    Print #TextFile, str
  
'Save & Close Text File
    Close TextFile

End Sub

Public Sub CreateText(pos1, pos2, pos3, str)
    Dim moSpace As AcadModelSpace
    Set moSpace = ThisDrawing.ModelSpace
    Dim TextPosition(0 To 2) As Double
    TextPosition(0) = pos1
    TextPosition(1) = pos2
    TextPosition(2) = pos3
    moSpace.AddText str, TextPosition, 1.5
End Sub

Public Sub CreateLine(x1, y1, z1, x2, y2, z2)
    Dim moSpace As AcadModelSpace
    Set moSpace = ThisDrawing.ModelSpace
    Dim startPoint(0 To 2) As Double, endPoint(0 To 2) As Double
    Dim LineObj As AcadLine
    startPoint(0) = x1: startPoint(1) = y1: startPoint(2) = z1
    endPoint(0) = x2: endPoint(1) = y2: endPoint(2) = x2
    Set LineObj = moSpace.AddLine(startPoint, endPoint)
End Sub

Public Sub CreatePoints(x, y, z)
    Dim moSpace As AcadModelSpace
    Set moSpace = ThisDrawing.ModelSpace
    Dim Point(0 To 2) As Double
    Dim PointObj As AcadPoint
    Point(0) = x: Point(1) = y: Point(2) = z
    Set PointObj = moSpace.AddPoint(Point)
End Sub

Public Sub CreateCircle(x1, y1, z1, x2, y2, z2)
    Dim circleObj As AcadCircle
    Dim centerPoint(0 To 2) As Double
    Dim radius As Double
    
    centerPoint(0) = x1: centerPoint(1) = y1: centerPoint(2) = z1
    radius = Distance2Points(x1, y1, x2, y2)
    
    Set circleObj = ThisDrawing.ModelSpace.AddCircle(centerPoint, radius)
    ZoomAll
End Sub

Public Function System2Equations(a1, b1, c1, a2, b2, c2) As Variant
    Dim result(0 To 1) As Double
    
    result(0) = (a1 * b2 * c1 - a2 * b1 * c1 - a1 * b1 * c2 + a2 * b1 * c1) / (a1 * a1 * b2 - a1 * a2 * b1)
    result(1) = (a1 * c2 - a2 * c1) / (a1 * b2 - a2 * b1)
    
    System2Equations = result
End Function

Public Function CalPerpPoint(pX, pY, pZ, lX1, lY1, lZ1, lX2, lY2, lZ2) As Variant
    abNVector1 = lX2 - lX1
    abNVector2 = lY2 - lY1
    abUVector1 = abNVector2
    abUVector2 = -abNVector1
    
    'an*x + bn*y = (an*xC + bn*yC) --(c)
    'au*x + bu*y = (au*xA + bu*yA) --(c)
    Dim d(0 To 1) As Double
    d(0) = System2Equations(abNVector1, abNVector2, abNVector1 * pX + abNVector2 * pY, abUVector1, abUVector2, abUVector1 * lX1 + abUVector2 * lY1)(0)
    d(1) = System2Equations(abNVector1, abNVector2, abNVector1 * pX + abNVector2 * pY, abUVector1, abUVector2, abUVector1 * lX1 + abUVector2 * lY1)(1)
    
    CalPerpPoint = d
End Function



Private Sub commandFrame_Click()

End Sub

Private Sub createLineButton_Click()
    Create2DLineForm.show
    CreateText lineX1, lineY1, 0, "A"
    CreateText lineX2, lineY2, 0, "B"
    ThisDrawing.SendCommand " "
End Sub

Public Function Distance2Points(x1, y1, x2, y2) As Double
    Distance2Points = Sqr((x2 - x1) ^ 2 + (y2 - y1) ^ 2)
End Function

Private Sub createPerpProjButton_Click()
    If (isAB = False Or isC = False) Then
            MsgBox "Cannot create D with AB: " & isAB & " and C: " & isC
            statusTextBox.Value = mainForm.statusTextBox.Value & "A 2d point has FAILED to be created because of not enough information" & vbCrLf
            statusTextBox.Value = mainForm.statusTextBox.Value & "At: " & Now() & vbCrLf & vbCrLf
        Else
            Dim x As Double
            Dim y As Double
        
            x = CalPerpPoint(pointX, pointY, 0, lineX1, lineY1, 0, lineX2, lineY2, 0)(0)
            y = CalPerpPoint(pointX, pointY, 0, lineX1, lineY1, 0, lineX2, lineY2, 0)(1)
            
            If (Distance2Points(lineX1, lineY1, x, y) > Distance2Points(lineX1, lineY1, lineX2, lineY2) Or Distance2Points(lineX2, lineY2, x, y) > Distance2Points(lineX1, lineY1, lineX2, lineY2)) Then
                    MsgBox "Cannot create D because D will be out of AB"
                    statusTextBox.Value = mainForm.statusTextBox.Value & "A 2d intersection point has FAILED to be created with (" & x & "," & y & ")" & vbCrLf
                    statusTextBox.Value = mainForm.statusTextBox.Value & "At: " & Now() & vbCrLf & vbCrLf
                Else
                    CreatePoints x, y, 0
                    CreateText x, y, 0, "D"
                    ThisDrawing.SendCommand " "
                    ZoomAll
                    
                    dX = x
                    dY = y
                    dZ = 0
                    
                    statusTextBox.Value = mainForm.statusTextBox.Value & "A 2D PERPENDICULAR PROJECTION has just created with (" & x & "," & y & ")" & vbCrLf
                    statusTextBox.Value = mainForm.statusTextBox.Value & "At: " & Now() & vbCrLf & vbCrLf
                    
                    MsgBox "Successfully created with D(" & x & ", " & y & ")"
                    dLabel.Caption = "D(" & Format(x, "0.00") & ", " & Format(y, "0.00") & ")"
                    
                    'Show hidden options
                    cdCheckBox.Visible = 1
                    circleCheckBox.Visible = 1
                    zoomCheckBox.Visible = 1
                    dOptionButton.Visible = 1
            End If
    End If
End Sub

Private Sub createPoint_Click()
    Create2DPointForm.show
    CreateText pointX, pointY, 0, "C"
    ThisDrawing.SendCommand " "
End Sub

Private Sub dOptionButton_Click()
    If (cdCheckBox.Value = True) Then
        CreateLine pointX, pointY, pointZ, dX, dY, dZ
        ThisDrawing.SendCommand " "
        ZoomAll
        
        statusTextBox.Value = mainForm.statusTextBox.Value & "A 2D LINE has just created by (" & pointX & "," & pointY & ") and (" & dX & "," & dY & ")" & vbCrLf
        statusTextBox.Value = mainForm.statusTextBox.Value & "At: " & Now() & vbCrLf & vbCrLf
    End If
    
    If (circleCheckBox.Value = True) Then
        CreateCircle pointX, pointY, 0, dX, dY, 0
        ThisDrawing.SendCommand " "
        ZoomAll
        
        statusTextBox.Value = mainForm.statusTextBox.Value & "A 2D CIRCLE has just created by (" & pointX & "," & pointY & ") and (" & dX & "," & dY & ") as radius" & vbCrLf
        statusTextBox.Value = mainForm.statusTextBox.Value & "At: " & Now() & vbCrLf & vbCrLf
    End If
    
    If (zoomCheckBox.Value = True) Then
        ThisDrawing.SendCommand "zoom extents "
        
        statusTextBox.Value = mainForm.statusTextBox.Value & "Zoomed extents" & vbCrLf
        statusTextBox.Value = mainForm.statusTextBox.Value & "At: " & Now() & vbCrLf & vbCrLf
    End If
End Sub

Private Sub UserForm_Terminate()
    CreateTextFile statusTextBox.Value
End Sub

Private Sub zoomCheckBox_Click()

End Sub
